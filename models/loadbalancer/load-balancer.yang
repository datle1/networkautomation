/*
  Copyright 2021 ManhVu

  Licensed under the Apache License, Version 2.0 (the "License");
  you may not use this file except in compliance with the License.
  You may obtain a copy of the License at

    http://www.apache.org/licenses/LICENSE-2.0

  Unless required by applicable law or agreed to in writing, software
  distributed under the License is distributed on an "AS IS" BASIS,
  WITHOUT WARRANTIES OR CONDITIONS OF ANY KIND, either express or
  implied.
  See the License for the specific language governing permissions and
  limitations under the License.
*/

module load-balancer {
    yang-version 1.1;
    namespace "urn:etsi:osm:yang:augments:load-balancer";
    prefix "load-balancer";

    import ietf-inet-types {
        prefix inet;
    }

    grouping admin-state-up {
      leaf admin-state-up {
        description
          "The administrative state of the resource, which is up (value:true) or down (value:false).";
        type boolean;
        default true;
      }
    }

    grouping loadbalancer-attributes {
      description "Load balancer attributes.";
      uses admin-state-up;

      leaf name {
        description
          "Name of the load balancer";
        type string;
      }

      leaf provider {
        description
          "Provider name for the load balancer.";
        mandatory true;
        type enumeration {
          enum "octavia";
          enum "a10";
        }
      }

      leaf address {
        description
          "The IP address of the loadbalancer";
        type inet:ip-address;
      }

      choice vip-network-input {
        description
          "There are three ways to specify a VIP network for the load balancer.";
        mandatory true;
        case port {
          leaf port-id {
            description
              "Providing a neutron port ID for the vip_port_id tells octavia to use this port for the VIP";
            type string;
          }
        }
        case subnet {
          leaf subnet-id {
            description
              "The ID of the subnet for the Virtual IP (VIP)";
            type string;
          }
        }
        case network {
          leaf network-id {
            description
              "The ID of the network for the Virtual IP (VIP).";
            type string;
          }
        }
      }
    }

    grouping listener-attributes {
      description "Listener attributes.";
      uses admin-state-up;
      leaf name {
        description "Name of the listener.";
        type string;
      }

      leaf protocol {
        description
          "The protocol for the resource. One of HTTP, HTTPS, SCTP, TCP, TERMINATED_HTTPS, or UDP.";
        type enumeration {
          enum UDP;
          enum TCP;
          enum HTTP;
          enum HTTPS;
        }
        default "HTTP";
      }

      leaf protocol-port {
        description
          "The protocol port number for the resource.";
        type uint16 {
            range 0..65535;
        }
      }

      leaf pool-name {
        description
          "Name of pool used by the listener.";
        type string;
      }

      leaf connection-limit {
        description
          "Maximum connections this load balancer can have. Default is infinite.";
        type int32 {
          range -1..65535;
        }
        default -1;
      }
    }

    grouping pool-attributes {
      description "Pool attributes.";
      uses admin-state-up;
      leaf name {
        description "Name of the pool.";
        type string;
      }

      leaf protocol {
        description
          "The protocol for the resource, either TCP or UDP.";
        type enumeration {
          enum TCP;
          enum UDP;
          enum HTTP;
          enum HTTPS;
        }
        mandatory true;
      }

      leaf protocol-port {
        description
          "The protocol port number for the resource.";
        type uint16 {
          range 0..65535;
        }
      }

      leaf lb-algorithm {
        description
          "The load balancing algorithm for the pool.";
        type enumeration {
          enum LEAST_CONNECTIONS;
          enum ROUND_ROBIN;
          enum SOURCE_IP;
          enum SOURCE_IP_PORT;
        }
        default "ROUND_ROBIN";
      }
    }

    grouping member-attributes {
      uses admin-state-up;
      leaf name {
        description
          "Name of the member.";
        type string;
      }

      leaf address {
        description
          "IP address of the member.";
        type inet:ip-address;
      }

      leaf weight {
        description
          "Weight of member.";
        type uint16 {
          range 0..256;
        }
        default 1;
      }
    }

    grouping healthmonitor-attributes {
      uses admin-state-up;
      leaf name {
        description
          "Name of the healthmonitor.";
        type string;
        mandatory true;
      }

      leaf protocol {
        description
          "Method to health check member status.";
        type enumeration {
          enum ICMP;
          enum UDP;
          enum TCP;
          enum HTTP;
          enum HTTPS;
        }
        default "ICMP";
      }

      leaf delay {
        description
          "The interval, in seconds, between health checks.";
        type uint32;
      }

      leaf timeout {
        description
          "The time, in seconds, after which a health check times out.";
        type uint32;
      }

      leaf retry-up {
        description
          "The number of successful checks before changing the operating status of the member to ONLINE. A valid value is from 1 to 10.";
        type uint16 {
          range 1..10;
        }
      }

      leaf retry-down {
        description
          "The number of allowed checks before changing the operating status of the member to ERROR. A valid value is from 1 to 10.";
        type uint16 {
          range 1..10;
        }
      }

    }
    grouping extended-load-balancer {
      container loadbalancer {
        presence true;
        uses loadbalancer-attributes;

        list listeners {
          key "name";
          uses listener-attributes;
        }

        list pools {
          key "name";
          uses pool-attributes;
          list members {
            key "name";
            uses member-attributes;
          }
          container healthmonitor {
            uses healthmonitor-attributes;
          }
        }
      }
    }
}
